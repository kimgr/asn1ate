TEST DEFINITIONS ::=
BEGIN
  value INTEGER ::= 128

  -- Single-value constraints apply to all types.
  ConstrainedInteger1 ::= INTEGER (50)
  ConstrainedInteger2 ::= INTEGER (value)
  ConstrainedInteger3 ::= INTEGER { one(10), two(20) } (10)
  ConstrainedInteger4 ::= INTEGER (100 | 50 | 25)

  ConstrainedBitString1 ::= BIT STRING { one(1), two(2) } (1)

  realValue REAL ::= 3.14
  ConstrainedReal1 ::= REAL (2.73)
  ConstrainedReal2 ::= REAL (realValue)
  ConstrainedReal3 ::= REAL (4E9)
  ConstrainedReal4 ::= REAL (2.73 | 3.14 | 1.23)

  Alias ::= OCTET STRING
  ConstrainedAlias ::= Alias (SIZE(8))

  PolicyQualifierId ::= OBJECT IDENTIFIER ( 1 | 0 )
END
