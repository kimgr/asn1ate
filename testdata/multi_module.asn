Module1 DEFINITIONS ::=
BEGIN

OneSequence ::= SEQUENCE {
    first INTEGER,
    second BOOLEAN
}

value INTEGER ::= 123

END


Module2 DEFINITIONS ::=
BEGIN

AnotherSequence ::= SEQUENCE {
    first INTEGER,
    second BOOLEAN
}

YetAnotherSequence ::= SEQUENCE {
    first [0] Module1.OneSequence,
    second [1] AnotherSequence
}

anothervalue INTEGER ::= Module1.value

END
