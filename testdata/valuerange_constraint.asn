TEST DEFINITIONS ::=
BEGIN
  -- Value range constraints apply to the following types.
  min INTEGER ::= 128
  max INTEGER ::= 256
  ConstraintedInteger1 ::= INTEGER(1..100)
  ConstraintedInteger2 ::= INTEGER(min..max)
  -- This is not yet translated in codegen
  -- ConstraintedInteger3 ::= INTEGER(MIN..MAX)

  realValue REAL ::= 3.14
  ConstrainedReal1 ::= REAL (0.12 .. 6.28)
  ConstrainedReal2 ::= REAL (realValue .. 9.21)
END
