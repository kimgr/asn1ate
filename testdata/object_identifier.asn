TEST DEFINITIONS ::=
BEGIN
  Foo ::= OBJECT IDENTIFIER

  Bar ::= SEQUENCE {
    oid OBJECT IDENTIFIER
  }

  Baz ::= CHOICE {
    oid OBJECT IDENTIFIER,
    id INTEGER
  }

  v0 OBJECT IDENTIFIER ::= { 1 }

  -- Value assignment, name and number form
  v1 OBJECT IDENTIFIER ::= {iso(1) member-body(2) us(840) rsadsi(113549)}

  -- Value assignment, number form
  v2 OBJECT IDENTIFIER ::= {1 2 840 113549}

  -- Value assignment, name form
  -- First three parts are known names, the last one a defined value.
  local INTEGER ::= 1234
  v3 OBJECT IDENTIFIER ::= {iso member-body us(840) local}

  -- Value assignment, mixed
  v4 OBJECT IDENTIFIER ::= {v1 723 local}

END
