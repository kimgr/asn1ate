TEST DEFINITIONS ::=
BEGIN
  -- Simple scalar types
  Bool ::= BOOLEAN
  Null ::= NULL
  Int ::= INTEGER
  Real ::= REAL
  BitString0 ::= BIT STRING

  RestrictedInteger ::= INTEGER {
    v1(1),
    v2(2)
  }

  -- Enumerated types
  BitString ::= BIT STRING {
    a(1),
    b(2)
  }

  Enumerated ::= ENUMERATED {
    a(1),
    b(2),
    c(3)
  }

  -- Constructed types
  Choice ::= CHOICE {
    a INTEGER,
    b BOOLEAN
  }

  Sequence ::= SEQUENCE {
    a INTEGER,
    b BOOLEAN,
    c BIT STRING
  }

  Set ::= SET {
    a INTEGER,
    b BOOLEAN
  }

  -- Collection types
  SequenceOf ::= SEQUENCE OF INTEGER
  SetOf ::= SET OF INTEGER

  -- Selection type
  Selection ::= a < Choice
  SelectedSequence ::= SEQUENCE {
    a a < Choice,
    b b < Choice
  }

  -- ANY type
  AnyType ::= ANY
  AnySeq ::= SEQUENCE {
     a INTEGER,
     b ANY DEFINED BY a
  }
END
