Test DEFINITIONS ::=
BEGIN
  -- Top-level
  Foo ::= SEQUENCE OF INTEGER

  -- Inline
  Bar ::= SEQUENCE
  {
    baz SEQUENCE OF INTEGER,  -- built-in type
    quux SEQUENCE OF Foo      -- user-defined type
  }

  -- Constraints handled in size_constraint.asn
END
