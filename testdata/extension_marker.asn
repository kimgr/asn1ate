TEST DEFINITIONS ::=
BEGIN

ChoiceType ::= CHOICE
{
  required1 INTEGER,
  required2 UTF8String,
  ...
}

SequenceType ::= SEQUENCE
{
  required1 INTEGER,
  required2 UTF8String,
  ...
}

-- I'm not sure if this is valid syntax, but I expect not.
-- The extension marker is likely only acceptable as the last
-- choice/sequence component.
PotentiallyInvalid ::= SEQUENCE
{
  required1 INTEGER,
  ...,
  required2 UTF8String
}

EnumType1 ::= ENUMERATED
{
  one (1),
  ...
}

EnumType2 ::= ENUMERATED
{
  two (2),
  ...,
  three (3)
}

EnumInSequence ::= SEQUENCE
{
  -- Check also the inline form of an enum
  foo ENUMERATED { zero(0), ..., one(1) }
}

END
