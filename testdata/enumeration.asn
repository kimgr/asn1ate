TEST DEFINITIONS ::=
BEGIN

EnumType1 ::= ENUMERATED
{
  one (1),
  two (2),
  three (3)
}

EnumType2 ::= ENUMERATED
{
  one,
  two,
  three
}

EnumType3 ::= ENUMERATED
{
  one,
  two(2),
  three
}

END
