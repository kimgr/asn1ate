TEST DEFINITIONS ::=
BEGIN
  -- Mostly a simple way to test that type
  -- translation in codegen happens correctly.
  OctetStr ::= OCTET STRING
  GeneralStr ::= GeneralString
  Utf8Str ::= UTF8String
  NumStr ::= NumericString
  PrintStr ::= PrintableString
  IA5Str ::= IA5String
  GraphStr ::= GraphicString
  VisibleStr ::= VisibleString
  TeletexStr ::= TeletexString
  UniversalStr ::= UniversalString
  BMPStr ::= BMPString
  T61Str ::= T61String
  VideotexStr ::= VideotexString
END
