Test DEFINITIONS ::=
BEGIN
  -- Top-level
  Foo ::= SET OF INTEGER

  -- Inline
  Bar ::= SEQUENCE
  {
    baz SET OF INTEGER,  -- built-in type
    quux SET OF Foo	 -- user-defined type
  }

  -- Constrained
  Baz ::= SEQUENCE SIZE(2..5) OF INTEGER

  Boo ::= SEQUENCE
  {
    monk SEQUENCE SIZE(0..10) OF INTEGER
  }
END
